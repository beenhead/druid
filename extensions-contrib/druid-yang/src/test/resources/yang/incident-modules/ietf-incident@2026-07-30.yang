module ietf-incident {
  yang-version 1.1;
  namespace "urn:ietf:params:xml:ns:yang:ietf-incident";
  prefix inc;

  import ietf-yang-types {
    prefix yang;
    reference
      "RFC 9911: Common YANG Data Types, Section 3";
  }
  import ietf-inet-types {
    prefix inet;
    reference
      "RFC 9911: Common YANG Data Types, Section 4";
  }
  import ietf-alarms {
    prefix al;
    reference
      "RFC 8632: A YANG Data Model for Alarm Management";
  }
  import ietf-network {
    prefix nw;
    reference
      "RFC 8345: A YANG Data Model for Network Topologies";
  }
  import ietf-yang-structure-ext {
    prefix sx;
    reference
      "RFC 8791: YANG Data Structure Extensions";
  }

  organization
    "IETF NMOP Working Group";
  contact
    "WG Web:   https://datatracker.ietf.org/wg/nmop/;
     WG List:  NMOP <mailto:nmop@ietf.org>

     Author:   Chong Feng
               <mailto:fengchongllly@gmail.com>
     Author:   Tong Hu
               <mailto:hutong@cmhi.chinamobile.com>
     Author:   Luis Miguel Contreras Murillo
        <mailto:luismiguel.contrerasmurillo@telefonica.com>
     Author:  Qin Wu
               <mailto:bill.wu@huawei.com>
     Author:   Nigel Davis
               <mailto:ndavis@ciena.com>";




  description
    "This module defines the interfaces for incident
     management lifecycle.

     This module is intended for the following use cases:
     * incident lifecycle management:
       - incident report: report incident instance to client
                      when an incident instance is detected.
       - incident acknowledge: acknowledge an incident instance.
       - incident diagnose: diagnose an incident instance.
       - incident resolve: resolve an incident instance.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-07-30 {
    description
      "Initial version.";
    reference
      "RFC XXXX: A YANG Data Model for Network Incident Management.";
  }

  // Identities

  identity incident-domain {
    description
      "The base identity to indicate the domain of
       an incident.";




  }

  identity single-domain {
    base incident-domain;
    description
      "Indicates single domain.";
  }

  identity access {
    base single-domain;
    description
      "Indicates access domain.";
  }

  identity ran {
    base access;
    description
      "Indicates a radio access network domain.";
  }

  identity transport {
    base single-domain;
    description
      "Indicates a transport domain.";
  }

  identity otn {
    base transport;
    description
      "Indicates an optical transport network domain.";
    reference
      "RFC 9376: Applicability of GMPLS for beyond 100 Gbit/s Optical
                Transport Network";
  }

  identity ip {
    base single-domain;
    description
      "Indicates an IP domain.";
    reference
      "RFC 1136: Administrative Domains and Routing Domains A Model
                 for Routing in the Internet";
  }

  identity ptn {
    base ip;
    description
      "Indicates a packet transport network domain.";




    reference
      "RFC 6373: MPLS Transport Profile (MPLS-TP) Control Plane
                 Framework";
  }

  identity cross-domain {
    base incident-domain;
    description
      "Indicates a cross domain.";
  }

  identity incident-category {
    description
      "The abstract identity for incident category.";
  }

  identity device {
    base incident-category;
    description
      "Device category.";
    reference
      "RFC 8348: A YANG Data Model for Hardware Management";
  }

  identity power-environment {
    base device;
    description
      "Power environment category.";
    reference
      "RFC 8348: A YANG Data Model for Hardware Management";
  }

  identity device-hardware {
    base device;
    description
      "Device hardware category.";
    reference
      "RFC 8348: A YANG Data Model for Hardware Management";
  }

  identity device-software {
    base device;
    description
      "Device software category.";
    reference
      "RFC 8348: A YANG Data Model for Hardware Management";
  }





  identity line-card {
    base device-hardware;
    description
      "Line card category.";
    reference
      "RFC 8348: A YANG Data Model for Hardware Management";
  }

  identity maintenance {
    base incident-category;
    description
      "Maintenance category.";
  }

  identity network {
    base incident-category;
    description
      "Network category.";
  }

  identity protocol {
    base incident-category;
    description
      "Protocol category.";
  }

  identity overlay {
    base incident-category;
    description
      "Overlay category.";
  }

  identity vm {
    base incident-category;
    description
      "Virtual Machine category.";
  }

  identity event-type {
    description
      "The abstract identity for Event type.";
    reference
      "RFC 9940: Some Key Terms for Network Fault and Problem
       Management";
  }

  identity alarm {
    base event-type;




    description
      "Alarm event type.";
    reference
      "RFC 8632: A YANG Data Model for Alarm Management";
  }

  identity link-down {
    base event-type;
    description
      "Link down event type.";
    reference
      "RFC 8632: A YANG Data Model for Alarm Management";
  }

  identity notif {
    base event-type;
    description
      "Notification event type.";
    reference
      "RFC 5277: NETCONF Event Notifications and
       RFC 8639: Subscription to YANG Notifications and
       RFC 8641: Subscription to YANG Notifications for
                 Datastore Updates and
       I-D.ietf-netconf-notif-envelope: Extensible YANG
                     Model for YANG-Push Notifications";
  }

  identity metric {
    base event-type;
    description
      "Metric event type.";
    reference
      "RFC 9375: A YANG Data Model for Network and VPN
                 Service Performance Monitoring";
  }

  identity unknown {
    base event-type;
    description
      "Unknown event type.";
  }

  identity incident-type {
    description
      "The abstract identity for Incident type.";
  }

  identity problem {




    base incident-type;
    description
      "It indicates the class of the incident is a problem
       (i.e., cause of the incident) for example an interface
       fails to work.";
    reference
      "RFC 9940: Some Key Terms for Network Fault and Problem
                 Management";
  }

  identity sla-violation {
    base incident-type;
    description
      "It indicates the class of the incident is an SLA
       violation, for example high CPU rate may cause
       a fault in the future.";
  }

  identity acknowledge-error {
    description
      "Base identity for the problem found while attempting
       to fulfill an 'incident-acknowledge' RPC request.";
  }

  identity diagnose-error {
    description
      "Base identity for the problem found while attempting
       to fulfill an 'incident-diagnose' RPC request.";
  }

  identity resolve-error {
    description
      "Base identity for the problem found while attempting
       to fulfill an 'incident-resolve' RPC request.";
  }

  identity repeated-acknowledge {
    base acknowledge-error;
    description
      "The incident that is referred to has already been
       acknowledged.";
  }

  identity incident-not-found {
    base acknowledge-error;
    base diagnose-error;
    base resolve-error;
    description




      "The incident is triggered when the incident does not
       exist in the datastore and a Client performs the RPCs.";
  }

  identity probable-cause-unlocated {
    base diagnose-error;
    description
      "Fail to locate the Probable Root Causes when performing
       the diagnosis operation. The detailed reason MUST be
       included in the 'description'.";
  }

  identity probable-cause-unresolved {
    base resolve-error;
    description
      "Fail to resolve the Probable Root Causes when performing
       the resolution operation. The detailed reason MUST be
       included in the 'description'.";
  }

  identity permission-denied {
    base diagnose-error;
    base resolve-error;
    description
      "The permission required for performing specific
       detection/resolution task is not granted.";
  }

  identity operation-timeout {
    base diagnose-error;
    base resolve-error;
    description
      "The diagnosis/resolution time exceeds the preset time.";
  }

  identity resource-unavailable {
    base diagnose-error;
    base resolve-error;
    description
      "The resource is unavailable to perform
       the diagnosis/resolution operation.";
  }

  identity cause-name {
    description
      "Base identity for the cause name.";
  }





  identity hardware-failure {
    base cause-name;
    description
      "It indicates the class of cause name is hardware
       failure.";
  }

  identity interface-hardware-failure {
    base hardware-failure;
    description
      "It indicates the class of cause name is the
       interface hardware failure.";
  }

  identity loss-of-signal {
    base cause-name;
    description
      "It indicates the class of cause name is the
       loss of signal.";
  }

  identity rt-misconfiguration {
    base cause-name;
    description
      "It indicates the class of cause name is
       routing protocol misconfiguration.";
  }

  identity service-misconfiguration {
    base cause-name;
    description
      "It indicates the class of cause name is service
       misconfiguration.";
  }

  identity tunnel-misconfiguration {
    base cause-name;
    description
      "It indicates the class of cause name is tunnel
       misconfiguration.";
  }

  identity protection-failure {
    base cause-name;
    description
      "It indicates the class of cause name is
       protection failure.";
  }




  // Typedefs

  typedef incident-priority {
    type enumeration {
      enum critical {
        description
          "The 'critical' priority level indicates that
           a service-affecting condition has occurred and
           an immediate corrective action is required.
           Such a priority can be reported, for example,
           when a resource becomes totally out of service
           and its capability must be restored.";
      }
      enum high {
        description
          "The 'high' priority level indicates that a
           service-affecting condition has developed and
           an urgent corrective action is required. Such
           a priority can be reported, for example, when
           there is a severe degradation in the capability
           of the resource and its full capability must be
           restored.";
      }
      enum medium {
        description
          "The 'medium' severity level indicates the
           existence of a non-service-affecting fault
           condition and that corrective action should
           be taken in order to prevent a more serious
          (for example, service-affecting) fault. Such
          a priority can be reported, for example, when
          the detected alarm condition is not currently
          degrading the capacity of the resource.";
      }
      enum low {
        description
          "The 'low' priority level indicates the detection of a
          potential or impending service-affecting fault, before any
          significant effects have been felt.  Action should be
          taken to further diagnose (if necessary) and correct the
          problem in order to prevent it from becoming a more
          serious service-affecting fault.";
      }
    }
    description
      "Defines the priority of incident.";
  }





  typedef incident-ref {
    type leafref {
      path "/inc:incidents/inc:incident/inc:incident-no";
      require-instance false;
    }
    description
      "Provides a reference to a network incident using
       incident-no note that incident no is unique but not
       incident list key. The incident-ref is used for
       correlation between incident no and incident list
       key in the RPCs and Notification.";
  }

  // Groupings

  grouping probable-cause-info {
    description
      "The information of Probable Root Cause.";
    leaf cause-name {
      type identityref {
        base cause-name;
      }
      description
        "Specifies the cause name.";
    }
    leaf detail {
      type string;
      description
        "The detail information of the cause.";
    }
  }

  grouping resources-info {
    description
      "The grouping which defines the network
       resources of a node.";
    uses nw:node-ref;
    list resource {
      key "name";
      description
        "The resources of a network node.";
      leaf name {
        type al:resource;
        description
          "Network resource name.";
      }
    }
  }




  grouping incident-time-info {
    description
      "The grouping defines incident time information.";
    leaf raise-time {
      type yang:date-and-time;
      description
        "The time when an incident instance is raised.";
    }
    leaf occur-time {
      type yang:date-and-time;
      mandatory true;
      description
        "The time when an incident instance occurs.
         It's the occur time of the first event during
         incident detection.";
    }
    leaf clear-time {
      type yang:date-and-time;
      description
        "The time when an incident instance is
         resolved.";
    }
    leaf ack-time {
      type yang:date-and-time;
      description
        "The time when an incident instance is
         acknowledged.";
    }
    leaf last-updated {
      type yang:date-and-time;
      description
        "The latest time when an incident instance is
         updated.";
    }
  }

  grouping incident-info {
    description
      "The grouping defines the information of an
       incident.";
    leaf name {
      type string;
      description
        "The name of an incident.";
    }
    leaf type {
      type identityref {
        base incident-type;




      }
      description
        "The type of an incident.";
    }
    leaf incident-qualifier {
      type string;
      description
        "The unique qualifier of an incident instance
         type. This leaf is used when the 'type' leaf
         cannot uniquely identify the incident instance
         type. Normally, this is not the case, and this
         leaf is the empty string.";
    }
    leaf-list service-instance {
      type string;
      description
        "The related network service instances of
         the incident instance.";
    }
    leaf domain {
      type identityref {
        base incident-domain;
      }
      mandatory true;
      description
        "The domain of an incident.";
    }
    leaf priority {
      type incident-priority;
      mandatory true;
      description
        "The priority of an incident instance.";
    }
    leaf status {
      type enumeration {
        enum raised {
          description
            "An incident instance is raised.";
        }
        enum updated {
          description
            "The information of an incident instance
             is updated.";
        }
        enum cleared {
          description
            "An incident is cleared.";
        }




      }
      description
        "The status of an incident instance.";
    }
    leaf ack-status {
      type enumeration {
        enum acknowledged {
          description
            "The incident has been acknowledged by user.";
        }
        enum unacknowledged {
          description
            "The incident hasn't been acknowledged.";
        }
      }
      description
        "The acknowledge status of an incident.";
    }
    leaf category {
      type identityref {
        base incident-category;
      }
      mandatory true;
      description
        "The category of an incident.";
    }
    leaf detail {
      type string;
      description
        "Detailed information of this incident.";
    }
    leaf resolve-advice {
      type string;
      description
        "The advice to resolve this incident.";
    }
    container sources {
      description
        "The source components.";
      list source {
        key "node-ref";
        description
          "The source components of incident. An Incident might
           be created even if we don't know yet the sources
           (hence we can not populate source list in the sources
           container). Therefore the min-elements for the source
           list is set to 0 which is default value. Once the
           Incident is diagnosed, the source(s) will be




           populated.";
        uses resources-info;
      }
    }
    container probable-causes {
      description
        "The Probable Root Cause objects.";
      list probable-cause {
        key "node-ref cause-name";
        description
          "The Probable Root Causes of incident.";
        uses resources-info {
          augment "resource" {
            description
              "Augment Probable Root Cause information.";
    //if Probable Root Cause object is a resource of a node
            uses probable-cause-info;
          }
        }
        //if Probable Root Cause object is a node
        uses probable-cause-info;
      }
    }
    container probable-events {
      description
        "The Probable Root Cause related events of the incident.";
      list probable-event {
        key "type event-id";
        description
          "The Probable Root Cause related event of the incident.";
        leaf type {
          type leafref {
            path "../../../events/event/type";
          }
          description
            "The event type.";
        }
        leaf event-id {
          type leafref {
            path "../../../events/event[type = current()/../type]"
               + "/event-id";
          }
          description
            "The event identifier, such as uuid,
             sequence number, etc.";
        }
      }
    }




    container events {
      description
        "Related events.";
      list event {
        key "type event-id";
        description
          "Related events.";
        leaf type {
          type identityref {
            base event-type;
          }
          description
            "Event type.";
        }
        leaf event-id {
          type string;
          description
            "The event identifier, such as uuid,
             sequence number, etc.";
        }
        choice event-type-info {
          description
            "Various different event type information.";
          case alarm {
            when "derived-from-or-self(type, 'alarm')" {
              description
                "Only applies when type is alarm.";
            }
            container alarm {
              description
                "Alarm type event.";
              leaf resource {
                type leafref {
                  path "/al:alarms/al:alarm-list/al:alarm"
                     + "/al:resource";
                  require-instance false;
                }
                description
                  "This is an identification of the alarming
                   resource.";
                reference
                  "RFC 8632: A YANG Data Model for Alarm
                   Management";
              }
              leaf alarm-type-id {
                type leafref {
                  path "/al:alarms/al:alarm-list/al:alarm"
                     + "[al:resource = current()/../resource]"




                     + "/al:alarm-type-id";
                  require-instance false;
                }
                description
                  "Alarm type id.";
                reference
                  "RFC 8632: A YANG Data Model for Alarm
                             Management";
              }
              leaf alarm-type-qualifier {
                type leafref {
                  path "/al:alarms/al:alarm-list/al:alarm"
                     + "[al:resource = current()/../resource]"
                     + "[al:alarm-type-id = current()/.."
                     + "/alarm-type-id]/al:alarm-type-qualifier";
                  require-instance false;
                }
                description
                  "Alarm type qualifier.";
                reference
                  "RFC 8632: A YANG Data Model for Alarm
                             Management";
              }
            }
          }
          case metric {
            when "derived-from-or-self(type, 'metric')" {
              description
                "Only applies when type is metric.";
            }
            container metric {
              description
                "Metric type event. Performance metrics
                 exceeding SLO thresholds.";
              leaf resource {
                type al:resource;
                description
                  "This is an identification of the network
                   resource such as interface, where the metric
                   can be collected or measured.";
                reference
                  "RFC 8632: A YANG Data Model for Alarm
                             Management";
              }
              leaf metric-name {
                type string;
                description
                  "Metric Name.";




              }
              leaf threshold-value {
                type decimal64 {
                  fraction-digits 2;
                }
                description
                  "Threshold value for the specific metric.";
              }
              leaf observed-value {
                type decimal64 {
                  fraction-digits 2;
                }
                description
                  "Observed value for the specific metric.";
              }
            }
          }
          case notification {
            when "derived-from-or-self(type, 'notif')" {
              description
                "Only applies when type is notification.";
            }
            container notification {
              description
                "Notification type event.";
              leaf event-time {
                type yang:date-and-time;
                description
                  "The date and time the event was generated by
                   the network node.";
                reference
                  "I-D.ietf-netconf-notif-envelope: Extensible
                   YANG Model for YANG-Push Notifications";
              }
              leaf hostname {
                type inet:host;
                description
                  "The hostname of the network node. This value
                   is usually configured on the node by the
                   administrator to identify the node in the
                   network uniquely.";
                reference
                  "I-D.ietf-netconf-notif-envelope: Extensible
                   YANG Model for YANG-Push Notifications";
              }
              leaf sequence-number {
                type yang:counter32;
                description




                  "Unique sequence number for each published
                   message by the publisher process. The initial
                   number is 1 and counts up by 1 at every
                   published notification message until it reaches
                   4294967295. Then, it wraps around and restarts
                   at 0. The value 0 is used to detect wrap
                   arounds.";
                reference
                  "I-D.ietf-netconf-notif-envelope: Extensible
                   YANG Model for YANG-Push Notifications";
              }
              anydata contents {
                description
                  "This contains the values defined by the
                   'notification' statement unchanged.";
              }
            }
          }
        }
      }
    }
  }

  // RPCs

  rpc incident-acknowledge {
    description
      "This rpc can be used to acknowledge the specified
       incidents.";
    input {
      leaf-list incident-no {
        type incident-ref;
        min-elements 1;
        description
          "The unique number of an incident instance
           based on the incident-no which is corresponding
           to the name type incident-id keys.";
      }
    }
  }

  rpc incident-diagnose {
    description
      "This rpc can be used to diagnose the specified
       incidents. The result of diagnosis will be reported
       by incident notification.";
    input {
      leaf-list incident-no {




        type incident-ref;
        min-elements 1;
        description
          "The unique number of an incident instance
           based on the incident-no which is corresponding
           to the name type incident-id keys.";
      }
    }
  }

  rpc incident-resolve {
    description
      "This rpc can be used to resolve the specified
       incidents. The result of resolution will be reported
       by incident notification.";
    input {
      leaf-list incident-no {
        type incident-ref;
        min-elements 1;
        description
          "The unique number of an incident instance
           based on the incident-no which is corresponding
           to the name type incident-id keys.";
      }
    }
  }

  sx:structure incident-acknowledge-error-info {
    container incident-acknowledge-error-info {
      description
        "This structure data must be inserted in the RPC
         error response to indicate the reason for the
         incident acknowledge failure.";
      leaf incident-no {
        type uint64;
        description
          "Indicate the incident instance identifier
           that fails the operation.";
      }
      leaf reason {
        type identityref {
          base acknowledge-error;
        }
        description
          "Indicates the reason why the operation
           is failed.";
      }
      leaf description {




        type string;
        description
          "Indicates the detailed description about
           the failure.";
      }
    }
  }
  sx:structure incident-diagnose-error-info {
    container incident-diagnose-error-info {
      description
        "This structure data must be inserted in
         the RPC error response to indicate the
         reason for the incident diagnose failure.";
      leaf incident-no {
        type uint64;
        description
          "Indicate the incident instance identifier
           that fails the operation.";
      }
      leaf reason {
        type identityref {
          base diagnose-error;
        }
        description
          "Indicates the reason why the operation
           is failed.";
      }
      leaf description {
        type string;
        description
          "Indicates the detailed description about
           the failure.";
      }
    }
  }
  sx:structure incident-resolve-error-info {
    container incident-resolve-error-info {
      description
        "This structure data must be inserted in
         the RPC error response to indicate the
         reason for the incident resolution failure.";
      leaf incident-no {
        type uint64;
        description
          "Indicate the incident instance identifier that
           fails the operation.";
      }
      leaf reason {




        type identityref {
          base resolve-error;
        }
        description
          "Indicates the reason why the operation is failed.";
      }
      leaf description {
        type string;
        description
          "Indicates the detailed description about the
           failure.";
      }
    }
  }

  // Notifications

  notification incident-notification {
    description
      "Incident notification. It will be triggered when
       the incident is raised, updated or cleared.";
    leaf incident-no {
      type incident-ref;
      mandatory true;
      description
        "The identifier of an incident instance. With
         incident-no used in both incident-notification
         and RPCs, an Incident Client know which notification
         is the result of a given RPC.";
    }
    uses incident-info;
    leaf time {
      type yang:date-and-time;
      description
        " The time when an incident instance occurs.
         It is the occur time of the first event during
         incident detection.";
    }
  }

  // Data definitions

  container incidents {
    config false;
    description
      "The information of incidents.";
    list incident {
      key "name type incident-qualifier";




      unique "incident-no";
      description
        "The information of incident.";
      leaf incident-no {
        type uint64;
        mandatory true;
        description
          "The unique identifier of the incident
           instance based on the name type
           incident-qualifier keys.";
      }
      uses incident-info;
      uses incident-time-info;
    }
  }
}
